module lsi-ivi-function-generator {
  yang-version 1.1;
  namespace "urn:lsi:params:xml:ns:yang:ivi-function-generator";
  prefix fgen;

  organization  "Lightside Instruments AS";

  description
    "Function generator management module designed
     after the IVI Fgen Class.";

  revision 2024-11-14 {
    description
      "Initial.";
  }

  feature measurement;

  //reference "IVI-4.3: Fgen Class Specification";

  container channels {
    list channel {
      key "name";
      leaf name {
        type string;
      }
      choice type {
        case standard-function-case {
          container standard-function {
            leaf waveform-type {
              mandatory true;
              type enumeration {
                enum dc;
                enum sine;
                enum square;
                enum triangle;
                enum ramp-up;
                enum ramp-down;
              }
            }
            leaf amplitude {
              description
                "Specifies the amplitude of the standard waveform the function generator produces. When the
                 Waveform attribute is set to Waveform DC, this attribute does not affect signal output. The units
                 are volts.";
              units "Volt";
              type decimal64 {
                fraction-digits 9;
              }
              default "1.00";
            }

            leaf dc-offset {
              description
                "Specifies the offset of the arbitrary waveform the function generator produces.";
              units "Volt";
              type decimal64 {
                fraction-digits 9;
              }
              default "0.00";
            }

            choice frequency-choice {
              case default-case {
                leaf frequency {
                  description
                    "Specifies the frequency at which the function generator produces its waveform.";
                  units "Samples per second";
                  type decimal64 {
                    fraction-digits 9;
                  }
                }
              }
              case sweep-case {
                leaf start-frequency {
                  description
                    "Specifies the start frequency of the sweep at which the function generator
                     produces its waveform.";
                  units "Samples per second";
                  type decimal64 {
                    fraction-digits 9;
                  }
                }
                leaf stop-frequency {
                  description
                    "Specifies the stop frequency at which the function generator
                     produces its waveform ../sweep-time seconds after starting the sweep.";
                  units "Samples per second";
                  type decimal64 {
                    fraction-digits 9;
                  }
                }
                leaf sweep-time {
                  description
                    "Specifies the sweep time or duration of the sweep
                     from start to stop frequency.";
                  units "seconds";
                  type decimal64 {
                    fraction-digits 9;
                  }
                }
              }
            }
            leaf duty-cycle-high {
              when '../waveform-type = "square"';
              description
                "Specifies the duty cycle for a square waveform. This attribute affects function generator behavior
                 only when the Waveform attribute is set to Waveform Square. The value is expressed as a
                 percentage.";

              units "Percent";
              type decimal64 {
                fraction-digits 9;
              }
            }
          }
        }
        case arbitrary-waveform-case {
          container arbitrary-waveform {
            leaf data {
              type binary;
              description
                "Specifies the array of data to use for the new arbitrary
                 waveform. The array’s elements must be normalized
                 between -1.00 and +1.00.

                 Double-precision floating point formated data according to IEEE 754.";
            }
            leaf gain {
              description
                "Specifies the gain of the arbitrary waveform the function generator produces.
                 This value is unitless.";
              type decimal64 {
                fraction-digits 9;
              }
              default "1.00";
            }
            leaf offset {
              description
                "Specifies the offset of the arbitrary waveform the function generator produces.";
              units "Volt";
              type decimal64 {
                fraction-digits 9;
              }
              default "0.00";
            }
            leaf sample-rate {
              description
                "Specifies the sample rate of the arbitrary waveforms the function generator produces.";
              units "Samples per second";
              type decimal64 {
                fraction-digits 9;
              }
            }
          }
        }
      }
    }
  }
}
