module lsi-ivi-dc-power {
  yang-version 1.1;
  namespace "urn:lsi:params:xml:ns:yang:ivi-dc-power";
  prefix dc-power;

  organization  "Lightside Instruments AS";

  description
    "DC power supplies management module designed
     after the IVI DC Power Supplies Class.";

  revision 2022-05-11 {
    description
      "Fixed config false statement. Now moved to /output-state";
  }

  feature measurement;

  //reference "IVI-4.4: IviDCPwr Class Specification";

  container outputs {
    list output {
      key "name";
      leaf name {
        type string;
      }
      leaf voltage-level {
        mandatory true;
        description
          "Specifies the voltage level the DC power supply attempts to generate.";
        units "Volt";
        type decimal64 {
          fraction-digits 9;
        }
      }
      leaf current-limit {
        mandatory true;
        description
          "Specifies the output current limit. The value of the Current Limit Behavior
           attribute determines the behavior of the power supply when the output current
           is equal to or greater than the value of this attribute.";
        units "Ampere";
        type decimal64 {
          fraction-digits 9;
        }
      }
    }
  }

  container outputs-state {
    config false;
    list output {
      key "name";
      leaf name {
        type string;
      }
      container measurement {
        if-feature "measurement";
        leaf voltage {
          units "Volt";
          type decimal64 {
            fraction-digits 9;
          }
        }
        leaf current {
          units "Ampere";
          type decimal64 {
            fraction-digits 9;
          }
        }
      }
    }
  }
}
