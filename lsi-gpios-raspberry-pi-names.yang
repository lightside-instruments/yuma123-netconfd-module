module lsi-gpios-raspberry-pi-names {
  yang-version 1.1;
  namespace "urn:lsi:params:xml:ns:yang:gpios-raspberry-pi-names";
  prefix gpios-names;

  import lsi-gpios {
    prefix gpios;
  }

  organization
    "Lightside Instruments AS";
  description
    "Deviation module with constrained GPIOs name set
     for Raspberry Pi.";

  revision 2023-04-27 {
    description
      "Initial.";
  }

  deviation "/gpios:gpios/gpios:gpio" {
    deviate add {
      must "name='0' "
         + "or name='1' "
         + "or name='2' "
         + "or name='3' "
         + "or name='4' "
         + "or name='5' "
         + "or name='6' "
         + "or name='7' "
         + "or name='8' "
         + "or name='9' "
         + "or name='10' "
         + "or name='11' "
         + "or name='12' "
         + "or name='13' "
         + "or name='14' "
         + "or name='15' "
         + "or name='16' "
         + "or name='17' "
         + "or name='18' "
         + "or name='19' "
         + "or name='20' "
         + "or name='21' "
         + "or name='22' "
         + "or name='23' "
         + "or name='24' "
         + "or name='25' "
         + "or name='26' "
         + "or name='27' " {
        error-message "Unsupported  name. Use one of the 28 available - 0, 1, ... 27";
      }
    }
  }
}
