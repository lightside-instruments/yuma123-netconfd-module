module lsi-display {
  yang-version 1.1;
  namespace "urn:lsi:params:xml:ns:yang:lsi-display";
  prefix display;

  organization  "Lightside Instruments AS";

  description
    "Display configuration and image data.";

  revision 2023-08-14 {
    description
      "Initial version.";
  }

  container displays {
    list display {
      key "name";
      leaf name {
        type string;
      }
      leaf image {
        mandatory "true";
        type binary;
      }
    }
  }
}
