module lsi-lights {
  yang-version 1.1;
  namespace "urn:lsi:params:xml:ns:yang:lights";
  prefix lights;

  organization
    "Lightside Instruments AS";
  description
    "Simple lights management model.";

  revision 2024-05-13 {
    description
      "Initial.";
  }

  container lights {
    list light {
      key "name";
      description
        "List of light sources.";
      leaf name {
        type string {
          length "1..10";
        }
      }
      choice type {
        case adjustable-rgb {
          leaf red {
            mandatory true;
            type uint8 {
              range "0..255";
            }
          }
          leaf green {
            mandatory true;
            type uint8 {
              range "0..255";
            }
          }
          leaf blue {
            mandatory true;
            type uint8 {
              range "0..255";
            }
          }
        }
      }
    }
  }
}
