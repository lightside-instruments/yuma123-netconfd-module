module lsi-thermometers {
  yang-version 1.1;
  namespace "urn:lsi:params:xml:ns:yang:thermometers";
  prefix thermometers;

  organization  "Lightside Instruments AS";

  description
    "Thermometers monitoring module.";

  revision 2022-07-25 {
    description
      "Initial version.";
  }

  container thermometers {
    config false;
    list thermometer {
      key "name";
      leaf name {
        type string;
      }
      leaf value {
        description
          "Temperature in degrees Celsius multiplied by 100.";
        type int32 {
          range "-27315..max";
        }
      }
    }
  }
}
