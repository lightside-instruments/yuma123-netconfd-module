module lsi-ivi-switch {
  yang-version 1.1;
  namespace "urn:lsi:params:xml:ns:yang:ivi-switch";
  prefix switch;

  organization  "Lightside Instruments AS";

  description
    "Switch management module designed after the IVI Switch Class.";

  revision 2022-04-07 {
    description
      "Initial version.";
  }

  //reference "IVI-4.6: IviSwtch Class Specification";

  container channels {
    list channel {
      key "name";
      leaf name {
        type string;
      }
      container connections {
        leaf-list connection {
          type leafref {
            path "/channels/channel/name";
            require-instance "true";
          }
        }
      }
    }
  }
}
