module lsi-gpios {
  yang-version 1.1;
  namespace "urn:lsi:params:xml:ns:yang:gpios";
  prefix gpios;

  organization
    "Lightside Instruments AS";
  description
    "Simple GPIOs management model.";

  revision 2024-05-13 {
    description
      "Initial.";
  }

  container gpios {
    list gpio {
      key "name";
      description
        "List of GPIOs configured as outputs.
         The remaining GPIOs not present in the list
         are configured as inputs.";
      leaf name {
        type string {
          length "1..10";
        }
      }
      choice direction {
        default "input";
        case input;
        case output {
          leaf level {
            mandatory true;
            description
              "Every output GPIO has to have a output level specified.";
            type uint32 {
              range "0..1";
            }
          }
        }
      }
    }
  }
  container gpios-state {
    config false;
    list gpio {
      key "name";
      description
        "List of all GPIOs available.";
      leaf name {
        type string;
      }
      leaf level {
        description
          "Signal level present on the GPIO.";
        type uint32 {
          range "0..1";
        }
      }
    }
  }
}
