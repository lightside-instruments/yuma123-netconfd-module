module lsi-ivi-scope {
  yang-version 1.1;
  namespace "urn:lsi:params:xml:ns:yang:ivi-scope";
  prefix scope;

  organization  "Lightside Instruments AS";

  description
    "Scope management module designed
     after the IVI Scope.";

  revision 2025-01-15 {
    description
      "Added /acquisition/channels/channel/range-used.";
  }

  feature measurement;

  //reference "IVI-4.1: Scope Class Specification";

  container acquisition {
    container channels {
      list channel {
        key "name";
        leaf name {
          type string;
        }
        leaf range {
          description
            "Specifies the absolute value of the full-scale input range
             for a channel. For example, to acquire a sine wave that
             spans between -5.0 and 5.0 volts, set the Vertical Range
             attribute to 10.0 volts.";
          units "Volt";
          type decimal64 {
            fraction-digits 9;
          }
        }

        leaf parameters {
          description
            "Specifies implementation specific parameters e.g. -c 2 -f S16_LE";
          type string;
        }

        leaf data {
          config false;
          type binary;
          description
            "Specifies the array of data to use for the new arbitrary
             waveform. The array’s elements must be normalized
             between -1.00 and +1.00.

             Double-precision floating point formated data according to IEEE 754.";
        }
        leaf range-used {
          config false;
          description
            "Specifies the actual adjusted channel range used
             during acquisition. It can be bigger then the
             configured range, but not smaller.";
          units "Volt";
          type decimal64 {
            fraction-digits 9;
          }
        }
      }
    }
    leaf sample-rate {
      description
        "Specifies the sample rate of the acquired waveform.";
      units "Samples per second";
      type decimal64 {
        fraction-digits 9;
      }
    }
    leaf samples {
      description
        "Specifies the number of sample points to be acquired for each channel.";
      type uint64;
    }

    leaf state {
      config false;
      type string;
    }
    container trigger {
      leaf source {
        type string;
      }
      leaf level {
        //mandatory true;
        description
          "Specifies the voltage threshold for the trigger sub-system.";
        units "Volts";
        type decimal64 {
          fraction-digits 9;
        }
      }
      leaf slope {
        //mandatory true;
        type enumeration {
          enum positive {
            description "A positive (rising) edge passing through the trigger level triggers the oscilloscope";
          }
          enum negative{
            description "A negative (falling) edge passing through the trigger level triggers the oscilloscope";
          }
        }
      }
    }
  }
  notification acquisition-complete {
    description
      "Sent when acquisition process is complete
       and data can be read.";
  }
}
