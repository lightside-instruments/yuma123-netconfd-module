module lsi-bar {
  yang-version 1.1;
  namespace "urn:lsi:params:xml:ns:yang:bar";
  prefix bar;

  organization  "Lightside Instruments AS";

  description
    "bar management module.";

  revision 2022-03-20 {
    description
      "Initial version.";
  }

  container bar {
    leaf enabled {
      type boolean;
    }
  }
}
